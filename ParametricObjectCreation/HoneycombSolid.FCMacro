"""
HoneycombSolid --> Honeycomb solid creator.
(c) 2021 Christian González Di Antonio <christiangda@gmail.com>

"""

__Name__ = 'HoneycombSolid'
__Comment__ = 'Macro to create a Honeycomb solid'
__Author__ = "Christian González Di Antonio <christiangda@gmail.com>"
__Version__ = 'v1.2.0'
__License__ = 'LGPL-2.0-or-later'
__Web__ = 'https://github.com/christiangda/FreeCAD-macros-HoneycombSolid'
__Wiki__ = 'https://github.com/christiangda/FreeCAD-macros-HoneycombSolid/blob/main/README.md'
__Icon__ = 'HoneycombSolid.xpm'
__Help__ = ''
__Status__ = 'Stable'
__Requires__ = ''
__Communication__ = 'https://github.com/FreeCAD/FreeCAD-macros/issues/'
__Files__ = 'honeycomb_solid/__init__.py,honeycomb_solid/honeycomb_solid.py'
__Xpm__ = '''
    /* XPM */
    static const char * ViewProviderHoneycombSolid_xpm[] = {
    "16 16 54 1",
    " 	c None",
    ".	c #181818",
    "+	c #5F5F5F",
    "@	c #636363",
    "#	c #353535",
    "$	c #474747",
    "%	c #434343",
    "&	c #606060",
    "*	c #424242",
    "=	c #111111",
    "-	c #444444",
    ";	c #151515",
    ">	c #3F3F3F",
    ",	c #1E1E1E",
    "'	c #1C1C1C",
    ")	c #1B1B1B",
    "!	c #2C2C2C",
    "~	c #535353",
    "{	c #0A0A0A",
    "]	c #363636",
    "^	c #383838",
    "/	c #2F2F2F",
    "(	c #252525",
    "_	c #555555",
    ":	c #393939",
    "<	c #515151",
    "[	c #262626",
    "}	c #161616",
    "|	c #464646",
    "1	c #4F4F4F",
    "2	c #545454",
    "3	c #3A3A3A",
    "4	c #131313",
    "5	c #121212",
    "6	c #5E5E5E",
    "7	c #0C0C0C",
    "8	c #0F0F0F",
    "9	c #0B0B0B",
    "0	c #0D0D0D",
    "a	c #1D1D1D",
    "b	c #292929",
    "c	c #3D3D3D",
    "d	c #222222",
    "e	c #171717",
    "f	c #1A1A1A",
    "g	c #282828",
    "h	c #272727",
    "i	c #5A5A5A",
    "j	c #3C3C3C",
    "k	c #595959",
    "l	c #616161",
    "m	c #505050",
    "n	c #2E2E2E",
    "o	c #565656",
    "   .+@@   #$    ",
    "    %@&* =-$    ",
    "    ;>,')!~&    ",
    "    {]^  /@@    ",
    "@   ($$   _@@   ",
    "@   :$    /@@   ",
    "<][}|1     2~3['",
    "445#6@     78889",
    "%  '&@@    #$   ",
    "$   $@@   0-$   ",
    "    a&@+  b$$   ",
    "     c*[de>_    ",
    "@    fgh {i@@   ",
    "@    ^$   j@@   ",
    "@@  4|$   {k@@  ",
    "lm ,n$     ]@o^["};
    '''

import FreeCAD as app


if __name__ == '__main__':
	# Running as a macro. Load as module, to support save-restore.
	try:
		from honeycomb_solid.honeycomb_solid import HoneycombSolid
		from honeycomb_solid.honeycomb_solid import ViewProviderHoneycombSolid
	except ImportError as err:
		app.Console.PrintError('Macro HoneycombSolid: failed to import module honeycomb_solid.honeycomb_solid\n')
	else:
		from honeycomb_solid.honeycomb_solid import makeHoneycombSolid
		makeHoneycombSolid(__Version__)
		if app.GuiUp:
			import FreeCADGui as gui
			gui.SendMsgToActiveView('ViewFit')
