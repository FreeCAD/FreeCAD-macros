# -*- coding: utf-8 -*-
# (c) 18Turbo, 2022

__Name__ = 'Generador3D'
__Comment__ = 'Create a solid with 2 or 3 sketches (views)'
__Author__ = '18Turbo'
__Version__ = '0.1.0'
__Date__ = '2022-09-05'
__License__ = 'LGPL-2.0-or-later'
__Web__ = 'https://github.com/18turbo/Generador3DFreeCAD'
__Wiki__ = 'https://github.com/18turbo/Generador3DFreeCAD/wiki'
__Icon__ = 'https://github.com/18turbo/Generador3DFreeCAD/blob/main/generador3D.svg'
__Help__ = ''
__Status__ = 'beta'
__Requires__ = 'FreeCAD >= v0.20'
__Contact__ = 'https://github.com/18turbo'
__Communication__ = 'https://github.com/18turbo/Generador3DFreeCAD/issues'
__Files__ = 'g3d/icons/g3d.svg,g3d/ui/g3d15.ui'


# (En español:)
# Funcionalidad:    Genera una pieza 3D a partir de 2 o 3 sketch, cada uno en una vista distinta (planta, frontal o lateral)
#
# Descripción:      Una vez ejecutada la macro, habrá que asociar cada sketch a cada vista, y pulsar el botón de OK.
#
#
# Notas de versiones:
# v.0.1.0:      Adaptación del código para varios idiomas
#               Corrección de error en la deselección de vistas
#               Cambio de nombres de ficheros
# v.0.0.16:     Corregido errores en la selección de vistas
#               Evita el error de introducir la longitud menor o igual al offset
# v.0.0.15:     Cambiada la interfaz
#               Añadido Offset y Longitud a cada vista
# v.0.0.14:     Adaptación al Addon Manager
# v.0.0.13:     Depuración de código
# v.0.0.12:     Depuración de código
#               Posibilidad de crear una carpeta automáticamente donde meter las vistas y ocultarlas
# v.0.0.11:     Incluida tolerancia 3D para evitar problemas en los límites.
# v.0.0.10:     Corrección de errores en sketch negativos
# v.0.0.9:      Cambio de interfaz y corrección de errores. Beta funcional.
# v.0.0.8:      Corrección de errores
# v.0.0.7:      Corrección de errores
# v.0.0.6:      Primera versión BETA
# v.0.0.5 ALFA: Genera la pieza 3D con 3 vistas
# v.0.0.4 ALFA: Arregla la selección en las vistas en la pestaña Task (Tarea)
#
#
# BetaTester: Rafael García Rodríguez
# BetaTester: 18Turbo

# Traducción inglés:    Rocco Vicedomini
 

import FreeCAD,FreeCADGui,Part

from PySide import QtCore, QtGui
from FreeCAD import Base



cadenasIdiomas = [
    [ # Español
        "Generador 3D",
        "Seleccione un sketch (boceto) en 2 o 3 vistas:",
        "Frontal -Alzado- (Front/Rear):",
        "Marque esta casilla si quiere activar la vista frontal y asígnele un sketch (boceto)",
        "Lateral -Perfil- (Right/Left):",
        "Marque esta casilla si quiere activar la vista lateral y asígnele un sketch (boceto)",
        "Planta -Sup/Inf- (Top/Bott):",
        "Marque esta casilla si quiere activar la vista en planta y asígnele un sketch (boceto)",
        "Tol. 3D (mm.):",
        "Es la distancia en mm. que extruirá de más. No debe influir en el objeto final. Si no desea tolerancia, ponga este valor a 0",
        "Crear un Grupo (Carpeta) para las vistas (sketches)",
        "Ocultar las vistas al generar el sólido",
        "Fusión (interesección)",
        "Versión:",
        "Información Breve de Uso:",
        "Cree un boceto (sketch) para cada vista con la que desee generar un sólido 3D. Necesitará al menos 2 bocetos.",
        "Luego pinche en el icono del script y seleccione un boceto para cada vista.",
        "Finalmente, pulse OK para generar el sólido.",
        "Documentación:",
        "Offset",
        "Es la distancia desde la cual empezará la extrusión en el eje Y (desplazamiento en Y)",
        "Longitud",
        "Es la distancia total de extrusión frontal (en el eje Y), que siempre será mayor que el Offset Frontal",
        "Offset",
        "Es la distancia desde la cual empezará la extrusión en el eje X (desplazamiento en X)",
        "Longitud",
        "Es la distancia total de extrusión lateral (en el eje X), que siempre será mayor que el Offset Lateral",
        "Offset",
        "Es la distancia desde la cual empezará la extrusión en el eje Z (desplazamiento en Z)",
        "Longitud",
        "Es la distancia total de extrusión en planta (en el eje Z), que siempre será mayor que el Offset en Planta",
        "Pieza3D",
        "VistasPieza3D"
    ],
    [ # English
        ## Strings for translation into any language (English Strings)

        "3D Generator",
        "Select a sketch in 2 or 3 views:",
        "Front view - (Front/Rear):",
        "Check this box if you want to activate the front view and assign it a sketch",
        "Side view - (Right/Left):",
        "Check this box if you want to activate the side view and assign it a sketch",
        "Plan view - (Top/Bott):",
        "Check this box if you want to activate the plan view and assign it a sketch",
        "Tol. 3D (mm.):",
        "Length in mm. This should not influence the final object. If you do not need this tolerance, set this value to 0",
        "Make a new group (folder) with views (sketches)",
        "Hide views when generating the solid",
        "Fusion (intersection)",
        "Version:",
        "Brief guide to use the script:",
        "Create a sketch for each view required to generate your 3D solid. At least two sketches will be required.",
        "Then click on the script icon and select a sketch for each view.",
        "Finally, press the OK button to generate the solid.",
        "Documentation:",
        "Offset",
        "Offset from the sketch plane from which the extrusion along the Y axis will start",
        "Length",
        "Total length of the frontal extrusion along the Y axis (it must be always larger than the frontal offset)",
        "Offset",
        "Offset from the sketch plane from which the extrusion along the X axis will start",
        "Length",
        "Total length of the lateral extrusion along the X axis (it must be always larger than the lateral offset)",
        "Offset",
        "Offset from the sketch plane from which the extrusion along the Z axis will start",
        "Length",
        "Total length of the vertical extrusion along the Z axis (it must be always larger than the vertical offset)",
        "3D-Part",
        "3D-Part_Views"
    ],
    [ ## Stringhe per la traduzione in qualsiasi lingua (stringhe in italiano)

        "Generatore 3D",
        "Seleziona uno schizzo in 2 o 3 viste:",
        "Vista frontale - (Fronte/Retro):",
        "Spunta questa casella se desideri utilizzare la vista frontale ed assegnarle uno schizzo",
        "Vista laterale - (Destra/Sinistra):",
        "Spunta questa casella se desideri utilizzare la vista laterale ed assegnarle uno schizzo",
        "Vista in pianta - (Alto/Basso):",
        "Spunta questa casella se desideri utilizzare la vista in pianta ed assegnarle uno schizzo",
        "Tol. 3D (mm.):",
        "Lunghezza in mm di sovraestrusione. Non dovrebbe influenzare l'oggetto finale. Se non si necessita questa tolleranza impostare il valore relativo a 0 mm",
        "Crea un nuovo gruppo (cartella) con le viste (sketch)",
        "Nasconde le viste quando viene generato il solido",
        "Fusione (intersezione)",
        "Versione:",
        "Breve guida all'uso dello script:",
        "Crea uno sketch per ogni vista necessaria a generare il solido. Sono necessari almeno due sketch.",
        "Quindi clicca sull'icona dello script e seleziona uno schizzo per ciascuna vista necessaria.",
        "Infine, premi il pulsante OK per generare il solido.",
        "Documentazione:",
        "Offset",
        "Distanza rispetto al piano dello sketch frontale da cui inizierà l'estrusione lungo l'asse Y (spostamento in Y)",
        "Lunghezza",
        "Lunghezza totale dell'estrusione frontale lungo l'asse Y (dovrà essere sempre più grande dell'offset frontale)",
        "Offset",
        "Distanza rispetto al piano dello sketch laterale da cui inizierà l'estrusione lungo l'asse X (spostamento in X)",
        "Lunghezza",
        "Lunghezza totale dell'estrusione laterale lungo l'asse X (dovrà essere sempre più grande dell'offset laterale)",
        "Offset",
        "Distanza rispetto al piano dello sketch in pianta da cui inizierà l'estrusione lungo l'asse Z (spostamento in Z)",
        "Lunghezza",
        "Lunghezza totale dell'estrusione verticale lungo l'asse Z (dovrà essere sempre più grande dell'offset in pianta)",
        "Pezzo3D",
        "Pezzo3D_Viste"
    ]
        ]



rutaMacro = FreeCAD.ParamGet("User parameter:BaseApp/Preferences/Macro")     
rutaUI = rutaMacro.GetString("MacroPath","") + "/g3d/ui/g3d15.ui"
rutaUI = rutaUI.replace("\\","/")

minimoExtrusion = 0.01


class g3d:

    def __init__(self):
        self.form = FreeCADGui.PySideUic.loadUi(rutaUI)
        
        lista = []
        self.nombrePlanta = ""
        self.nombreFrontal = ""
        self.nombreLateral = ""
        self.frontal = False
        self.lateral = False
        self.planta = False
        self.vistasActivas = 0

        for buscandoBocetos in objetos:
            if buscandoBocetos.TypeId.find('Sketcher::') > -1:
                lista.append(buscandoBocetos.Label)

        for i in lista:
            self.form.listWidgetFrontal.addItem(i)
            self.form.listWidgetLateral.addItem(i)
            self.form.listWidgetPlanta.addItem(i)

        self.form.listWidgetFrontal.itemSelectionChanged.connect(self.cambiaSeleccionFrontal)
        self.form.listWidgetLateral.itemSelectionChanged.connect(self.cambiaSeleccionLateral)
        self.form.listWidgetPlanta.itemSelectionChanged.connect(self.cambiaSeleccionPlanta)

        self.form.offsetF.valueChanged.connect(self.cambiaValorFrontal)
        self.form.offsetL.valueChanged.connect(self.cambiaValorLateral)
        self.form.offsetP.valueChanged.connect(self.cambiaValorPlanta)

        self.form.etFrontal.clicked.connect(self.cambiaCheckedFrontal)
        self.form.etLateral.clicked.connect(self.cambiaCheckedLateral)
        self.form.etPlanta.clicked.connect(self.cambiaCheckedPlanta)

        
        self.inicializarCadenas()

    def inicializarCadenas(self):
        traducir = self.traducir
        self.form.setWindowTitle(__Name__ + " " + titulo)
        self.form.etInfo.setText(traducir(idioma,"Seleccione un sketch (boceto) en 2 o 3 vistas:"))
        self.form.etFrontal.setTitle(traducir(idioma,"Frontal -Alzado- (Front/Rear):"))
        self.form.etFrontal.setToolTip(traducir(idioma,"Marque esta casilla si quiere activar la vista frontal y asígnele un sketch (boceto)"))
        self.form.etLateral.setTitle(traducir(idioma,"Lateral -Perfil- (Right/Left):"))
        self.form.etLateral.setToolTip(traducir(idioma,"Marque esta casilla si quiere activar la vista lateral y asígnele un sketch (boceto)"))
        self.form.etPlanta.setTitle(traducir(idioma,"Planta -Sup/Inf- (Top/Bott):"))
        self.form.etPlanta.setToolTip(traducir(idioma,"Marque esta casilla si quiere activar la vista en planta y asígnele un sketch (boceto)"))
        self.form.etTolerancia.setText(traducir(idioma,"Tol. 3D (mm.):"))
        self.form.etTolerancia.setToolTip(traducir(idioma,"Es la distancia en mm. que extruirá de más. No debe influir en el objeto final. Si no desea tolerancia, ponga este valor a 0"))
        self.form.meterVistasCarpeta.setText(traducir(idioma,"Crear un Grupo (Carpeta) para las vistas (sketches)"))
        self.form.ocultarVistas.setText(traducir(idioma,"Ocultar las vistas al generar el sólido"))
        self.form.radioInterseccion.setText(traducir(idioma,"Fusión (interesección)"))
        self.form.etVersion.setText(traducir(idioma,"Versión:"))
        self.form.etNumVersion.setText(__Version__ + " " + __Status__)
        self.form.etInfoUso.setText(traducir(idioma,"Información Breve de Uso:"))
        descripcionInfoUso = (traducir(idioma,"Cree un boceto (sketch) para cada vista con la que desee generar un sólido 3D. Necesitará al menos 2 bocetos.")
                + " " + traducir(idioma,"Luego pinche en el icono del script y seleccione un boceto para cada vista.")
                + " " + traducir(idioma,"Finalmente, pulse OK para generar el sólido."))
        self.form.descInfoUso.setText(descripcionInfoUso)
        self.form.etDoc.setText(traducir(idioma,"Documentación:"))
        self.form.etOffsetF.setText(traducir(idioma,"Offset"))
        self.form.etOffsetF.setToolTip(traducir(idioma,"Es la distancia desde la cual empezará la extrusión en el eje Y (desplazamiento en Y)"))
        self.form.offsetF.setToolTip(traducir(idioma,"Es la distancia desde la cual empezará la extrusión en el eje Y (desplazamiento en Y)"))
        self.form.etOffsetL.setText(traducir(idioma,"Offset"))
        self.form.etOffsetL.setToolTip(traducir(idioma,"Es la distancia desde la cual empezará la extrusión en el eje X (desplazamiento en X)"))
        self.form.offsetL.setToolTip(traducir(idioma,"Es la distancia desde la cual empezará la extrusión en el eje X (desplazamiento en X)"))
        self.form.etOffsetP.setText(traducir(idioma,"Offset"))
        self.form.etOffsetP.setToolTip(traducir(idioma,"Es la distancia desde la cual empezará la extrusión en el eje Z (desplazamiento en Z)"))
        self.form.offsetP.setToolTip(traducir(idioma,"Es la distancia desde la cual empezará la extrusión en el eje Z (desplazamiento en Z)"))
        self.form.etLongitudF.setText(traducir(idioma,"Longitud"))
        self.form.etLongitudF.setToolTip(traducir(idioma,"Es la distancia total de extrusión frontal (en el eje Y), que siempre será mayor que el Offset Frontal"))
        self.form.longF.setToolTip(traducir(idioma,"Es la distancia total de extrusión frontal (en el eje Y), que siempre será mayor que el Offset Frontal"))
        self.form.etLongitudL.setText(traducir(idioma,"Longitud"))
        self.form.etLongitudL.setToolTip(traducir(idioma,"Es la distancia total de extrusión lateral (en el eje X), que siempre será mayor que el Offset Lateral"))
        self.form.longL.setToolTip(traducir(idioma,"Es la distancia total de extrusión lateral (en el eje X), que siempre será mayor que el Offset Lateral"))
        self.form.etLongitudP.setText(traducir(idioma,"Longitud"))
        self.form.etLongitudP.setToolTip(traducir(idioma,"Es la distancia total de extrusión en planta (en el eje Z), que siempre será mayor que el Offset en Planta"))
        self.form.longP.setToolTip(traducir(idioma,"Es la distancia total de extrusión en planta (en el eje Z), que siempre será mayor que el Offset en Planta"))


    def traducir(self,idi,cad):
        if (idi == 0):
            return cad
        else:
            primerIdioma = cadenasIdiomas [0]
            indice = primerIdioma.index(cad)
            if indice > -1:
                return cadenasIdiomas [idi] [indice]
            else:
                return cad

    def cambiaValorFrontal(self):
        self.form.longF.setMinimum(self.form.offsetF.value() + minimoExtrusion)
    def cambiaValorLateral(self):
        self.form.longL.setMinimum(self.form.offsetL.value() + minimoExtrusion)
    def cambiaValorPlanta(self):
        self.form.longP.setMinimum(self.form.offsetP.value() + minimoExtrusion)

    def cambiaCheckedFrontal(self):
        if not self.form.etFrontal.isChecked():
            self.frontal = False
            self.vistasActivas = self.vistasActivas - 1
        else:
            self.frontal = True
            self.vistasActivas = self.vistasActivas + 1
    def cambiaCheckedLateral(self):
        if not self.form.etLateral.isChecked():
            self.lateral = False
            self.vistasActivas = self.vistasActivas - 1
        else:
            self.lateral = True
            self.vistasActivas = self.vistasActivas + 1
    def cambiaCheckedPlanta(self):
        if not self.form.etPlanta.isChecked():
            self.planta = False
            self.vistasActivas = self.vistasActivas - 1
        else:
            self.planta = True
            self.vistasActivas = self.vistasActivas + 1

    def cambiaSeleccionFrontal(self):
        self.nombreFrontal = str(self.form.listWidgetFrontal.selectedItems()[0].text())
    def cambiaSeleccionLateral(self):
        self.nombreLateral = str(self.form.listWidgetLateral.selectedItems()[0].text())
    def cambiaSeleccionPlanta(self):
        self.nombrePlanta = str(self.form.listWidgetPlanta.selectedItems()[0].text())

    def extrusion(self,nombreExtrusion,nombreEnVista,vista):
        App.ActiveDocument.addObject('Part::Extrusion',nombreExtrusion)
        f = App.ActiveDocument.getObject(nombreExtrusion)
        objf = App.ActiveDocument.getObjectsByLabel(nombreEnVista)
        f.Base = App.ActiveDocument.getObject(objf[0].Name)
        f.DirMode = "Custom"
        if vista == "planta":
            offset = self.form.offsetP.value()
            longitud = self.form.longP.value()
            f.Dir = App.Vector(0.000000000000000,0.000000000000000,1.000000000000000)
            if self.lateral:
               objetoLateral = App.ActiveDocument.getObjectsByLabel(self.nombreLateral)[0]
               maximoLZ = objetoLateral.Shape.BoundBox.ZMax
               minimoLZ = objetoLateral.Shape.BoundBox.ZMin
               if abs(maximoLZ) > abs(minimoLZ):
                   f.LengthFwd = (abs(maximoLZ) + self.form.tolerancia.value()) *2
               else:
                   f.LengthFwd = (abs(minimoLZ) + self.form.tolerancia.value()) *2
            else:
               objetoFrontal = App.ActiveDocument.getObjectsByLabel(self.nombreFrontal)[0]
               maximoFZ = objetoFrontal.Shape.BoundBox.ZMax
               minimoFZ = objetoFrontal.Shape.BoundBox.ZMin
               if abs(maximoFZ) > abs(minimoFZ):
                   f.LengthFwd = (abs(maximoFZ) + self.form.tolerancia.value()) *2
               else:
                   f.LengthFwd = (abs(minimoFZ) + self.form.tolerancia.value()) *2

        elif vista == "frontal":
            offset = self.form.offsetF.value()
            longitud = self.form.longF.value()
            f.Dir = App.Vector(0.000000000000000,1.000000000000000,0.000000000000000)
            if self.lateral:
                objetoLateral = App.ActiveDocument.getObjectsByLabel(self.nombreLateral)[0]
                maximoLY = objetoLateral.Shape.BoundBox.YMax
                minimoLY = objetoLateral.Shape.BoundBox.YMin
                if abs(maximoLY) > abs(minimoLY):
                    f.LengthFwd = (abs(maximoLY) + self.form.tolerancia.value()) *2
                else:
                    f.LengthFwd = (abs(minimoLY) + self.form.tolerancia.value()) *2
            else:
                objetoPlanta = App.ActiveDocument.getObjectsByLabel(self.nombrePlanta)[0]
                maximoPY = objetoPlanta.Shape.BoundBox.YMax
                minimoPY = objetoPlanta.Shape.BoundBox.YMin
                if abs(maximoPY) > abs(minimoPY):
                    f.LengthFwd = (abs(maximoPY) + self.form.tolerancia.value()) *2
                else:
                    f.LengthFwd = (abs(minimoPY) + self.form.tolerancia.value()) *2

        elif vista == "lateral":
            offset = self.form.offsetL.value()
            longitud = self.form.longL.value()
            f.Dir = App.Vector(1.000000000000000,0.000000000000000,0.000000000000000)
            if self.planta:
                objetoPlanta = App.ActiveDocument.getObjectsByLabel(self.nombrePlanta)[0]
                maximoPX = objetoPlanta.Shape.BoundBox.XMax
                minimoPX = objetoPlanta.Shape.BoundBox.XMin
                if abs(maximoPX) > abs(minimoPX):
                    f.LengthFwd = (abs(maximoPX) + self.form.tolerancia.value()) *2
                else:
                    f.LengthFwd = (abs(minimoPX) + self.form.tolerancia.value()) *2
            else:
                objetoFrontal = App.ActiveDocument.getObjectsByLabel(self.nombreFrontal)[0]
                maximoFX = objetoFrontal.Shape.BoundBox.XMax
                minimoFX = objetoFrontal.Shape.BoundBox.XMin
                if abs(maximoFX) > abs(minimoFX):
                    f.LengthFwd = (abs(maximoFX) + self.form.tolerancia.value()) *2
                else:
                    f.LengthFwd = (abs(minimoFX) + self.form.tolerancia.value()) *2

        f.DirLink = None        
        f.Solid = True
        f.Reversed = False
        if (offset>0) or (longitud>0):
            f.Symmetric = False
            f.LengthRev = offset * (-1)
            if (longitud>0):
                f.LengthFwd = longitud
        else:
            f.LengthRev = 0.000000000000000
            f.Symmetric = True
        f.TaperAngle = 0.000000000000000
        f.TaperAngleRev = 0.000000000000000
        App.ActiveDocument.recompute()
        return f

    def accept(self):
        #Comprobar que no existe ya una extrusión con este nombre
        numeroCoincidencias = 0
        encontradoCoincidencia = False
        cadenaAdicional = ""
        #objetos = FreeCAD.ActiveDocument.Objects
        for objeto in objetos:
            if ((objeto.Name.find('ExtrPlanta18Turbo') > -1) or 
               (objeto.Name.find('ExtrFrontal18Turbo') > -1) or
               (objeto.Name.find('ExtrLateral18Turbo') > -1)):
               numeroCoincidencias = numeroCoincidencias +1
               encontradoCoincidencia = True
        if encontradoCoincidencia:
            cadenaAdicional = cadenaAdicional + str(numeroCoincidencias)

        if (self.vistasActivas >= 2):
            if self.planta:
                # Sketch en Z (Planta XY)
                planta = self.extrusion("ExtrPlanta18Turbo" + cadenaAdicional,self.nombrePlanta,"planta")
            if self.frontal:
                # Sketch en Y (Frontal XZ)
                frontal = self.extrusion("ExtrFrontal18Turbo" + cadenaAdicional,self.nombreFrontal,"frontal")
            if self.lateral:
                # Sketch en X (Lateral YZ)
                lateral = self.extrusion("ExtrLateral18Turbo" + cadenaAdicional,self.nombreLateral,"lateral")

            # Intersección
            nombreInterseccion = self.traducir(idioma,"Pieza3D") + cadenaAdicional
            if (self.vistasActivas == 3):
                App.activeDocument().addObject("Part::MultiCommon",nombreInterseccion)
                App.ActiveDocument.getObject(nombreInterseccion).Shapes = [planta,frontal,lateral,]
            else:
                App.activeDocument().addObject("Part::MultiCommon",nombreInterseccion)
                if (self.planta) and (self.frontal):
                    App.ActiveDocument.getObject(nombreInterseccion).Shapes = [planta,frontal,]
                if (self.planta) and (self.lateral):
                   App.ActiveDocument.getObject(nombreInterseccion).Shapes = [planta,lateral,]
                if (self.frontal) and (self.lateral):
                   App.ActiveDocument.getObject(nombreInterseccion).Shapes = [frontal,lateral,]
            App.ActiveDocument.recompute()

            #Meter vistas en Grupo (Carpeta)
            if self.form.meterVistasCarpeta.checkState():
                nombreGrupoVistas = self.traducir(idioma,"VistasPieza3D") + cadenaAdicional
                App.activeDocument().Tip = App.activeDocument().addObject('App::DocumentObjectGroup',nombreGrupoVistas)
                if (self.planta):
                    objetoPlanta = App.ActiveDocument.getObjectsByLabel(self.nombrePlanta)[0]
                    App.ActiveDocument.getObject(nombreGrupoVistas).addObject(objetoPlanta)
                if (self.frontal):
                    objetoFrontal = App.ActiveDocument.getObjectsByLabel(self.nombreFrontal)[0]
                    App.ActiveDocument.getObject(nombreGrupoVistas).addObject(objetoFrontal)
                if (self.lateral):
                    objetoLateral = App.ActiveDocument.getObjectsByLabel(self.nombreLateral)[0]
                    App.ActiveDocument.getObject(nombreGrupoVistas).addObject(objetoLateral)
            #Ocultar Vistas
            if (self.form.ocultarVistas.isChecked()):
                if (self.planta):
                    objetoPlanta.Visibility = False
                if (self.frontal):
                    objetoFrontal.Visibility = False
                if (self.lateral):
                    objetoLateral.Visibility = False

        FreeCADGui.Control.closeDialog()
 


objetos = FreeCAD.ActiveDocument.Objects
# Se define el idioma con variable global
nombreIdioma = App.Gui.getLocale()
if nombreIdioma.find("English") > -1: idioma = 1
elif nombreIdioma.find("Spanish") > -1: idioma = 0
elif nombreIdioma.find("Italian") > -1: idioma = 2
else:
    idioma = 0
if idioma != 0:
    titulo = "(" + cadenasIdiomas [idioma][0] + ")"
else:
    titulo = ""      
panel = g3d()
FreeCADGui.Control.showDialog(panel)
