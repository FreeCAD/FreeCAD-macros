# -*- coding: utf-8 -*-

# Form implementation generated from reading ui file 'geodesic_dialog.ui'
# And changed manually to use FreeCAD "Gui::InputField"
# Created: Sun Jan  4 22:20:58 2015
#      by: pyside-uic 0.2.15 running on PySide 1.2.2
#
#
'''
************************************************************************
* Copyright (c)2015 Ulrich Brammer <ulrich1a[at]users.sourceforge.net> *
*                                                                      *
* This file is a supplement to the FreeCAD CAx development system.     *
*                                                                      *
* This program is free software; you can redistribute it and/or modify *
* it under the terms of the GNU Lesser General Public License (LGPL)   *
* as published by the Free Software Foundation; either version 2 of    *
* the License, or (at your option) any later version.                  *
* for detail see the LICENCE text file.                                *
*                                                                      *
* This software is distributed in the hope that it will be useful,     *
* but WITHOUT ANY WARRANTY; without even the implied warranty of       *
* MERCHANTABILITY or FITNESS FOR A PARTICULAR PURPOSE.  See the        *
* GNU Library General Public License for more details.                 *
*                                                                      *
* You should have received a copy of the GNU Library General Public    *
* License along with this macro; if not, write to the Free Software    *
* Foundation, Inc., 59 Temple Place, Suite 330, Boston, MA  02111-1307 *
* USA                                                                  *
*                                                                      *
************************************************************************
'''
__Name__ = 'Geodesic Dome'
__Comment__ = 'Geodesic Dome'
__Author__ = 'Ulrich Brammer'
__Version__ = '0.0.2'
__Date__ = '2019-02-02'
__License__ = 'LGPL-2.0-or-later'
__Web__ = ''
__Wiki__ = ''
__Icon__ = ''
__Help__ = ''
__Status__ = ''
__Requires__ = ''
__Communication__ = 'https://github.com/FreeCAD/FreeCAD-macros/issues/'
__Files__ = ''

# TODO: Create document if no opened document.

import math
import sys

import FreeCAD as app
import FreeCADGui as gui
from PySide import QtCore, QtGui
import Part

try:
    _encoding = QtGui.QApplication.UnicodeUTF8
    def tr(context, text):
        return QtGui.QApplication.translate(context, text, None, _encoding)
except AttributeError:
    def tr(context, text):
        return QtGui.QApplication.translate(context, text, None)


def say(s):
    app.Console.PrintMessage(str(s)+"\n")


def sayexc(mess=''):
    exc_type, exc_value, exc_traceback = sys.exc_info()
    ttt = repr(traceback.format_exception(exc_type, exc_value, exc_traceback))
    lls = eval(ttt)
    app.Console.PrintError(mess + "\n" + "-->  ".join(lls))


class Ui_Dialog(object):
    def setupUi(self, Dialog):
        Dialog.setObjectName("Dialog")
        Dialog.resize(477, 188)
        self.dia = Dialog
        self.gridLayoutWidget = QtGui.QWidget(Dialog)
        self.gridLayoutWidget.setGeometry(QtCore.QRect(19, 19, 440, 141))
        self.gridLayoutWidget.setObjectName("gridLayoutWidget")
        self.gridLayout = QtGui.QGridLayout(self.gridLayoutWidget)
        self.gridLayout.setContentsMargins(0, 0, 0, 0)
        self.gridLayout.setObjectName("gridLayout")
        self.label = QtGui.QLabel(self.gridLayoutWidget)
        self.label.setObjectName("label")
        self.gridLayout.addWidget(self.label, 0, 0, 1, 1)
        #self.lineEdit = QtGui.QLineEdit(self.gridLayoutWidget)
        fui = gui.UiLoader()
        self.lineEdit = fui.createWidget("Gui::InputField")

        self.lineEdit.setObjectName("lineEdit")
        self.gridLayout.addWidget(self.lineEdit, 0, 1, 1, 1)
        self.label_2 = QtGui.QLabel(self.gridLayoutWidget)
        self.label_2.setObjectName("label_2")
        self.gridLayout.addWidget(self.label_2, 1, 0, 1, 1)
        self.lineEdit_2 = QtGui.QLineEdit(self.gridLayoutWidget)
        self.lineEdit_2.setObjectName("lineEdit_2")
        self.gridLayout.addWidget(self.lineEdit_2, 1, 1, 1, 1)
        self.label_3 = QtGui.QLabel(self.gridLayoutWidget)
        self.label_3.setObjectName("label_3")
        self.gridLayout.addWidget(self.label_3, 2, 0, 1, 1)
        self.buttonBox = QtGui.QDialogButtonBox(self.gridLayoutWidget)
        self.buttonBox.setOrientation(QtCore.Qt.Horizontal)
        self.buttonBox.setStandardButtons(
            QtGui.QDialogButtonBox.Cancel|QtGui.QDialogButtonBox.Ok)
        self.buttonBox.setObjectName("buttonBox")
        self.gridLayout.addWidget(self.buttonBox, 2, 1, 1, 1)

        self.retranslateUi(Dialog)
        QtCore.QObject.connect(
            self.buttonBox, QtCore.SIGNAL("accepted()"), self.makeSomething)
        QtCore.QObject.connect(
            self.buttonBox, QtCore.SIGNAL("rejected()"), self.makeNothing)
        QtCore.QMetaObject.connectSlotsByName(Dialog)

    def retranslateUi(self, Dialog):
        Dialog.setWindowTitle(tr("GeodesicDome", "Geodesic Dome Creator"))
        self.label.setText(tr("GeodesicDome", "Dome Radius"))
        self.label_2.setText(tr("GeodesicDome",
                                "Frequency Parameter\n(Integer between 1 to 10)"))
        self.label_3.setText(tr("GeodesicDome",
                                "This Macro creates \na full geodesic dome shell.\nX-Y-symmetry plane \nfor even frequencies"))

    def makeSomething(self):
        say("Accepted! Dome radius: {} with frequency {}".format(
           self.lineEdit.property("text"),
           int(self.lineEdit_2.text())))

        doc = App.activeDocument()
        label = "GeodesicDome"

        theDome = doc.addObject("Part::Feature",label)
        radius = self.lineEdit.property("text")
        frequency = int(self.lineEdit_2.text())

        self.dia.close()
        self.makeDome(theDome, radius, frequency)
        doc.recompute()

    def makeNothing(self):
        say("Rejected!!")
        self.dia.close()

    def makeDome(self, obj, domeRad_str, ny):
        def makeFreqFaces(fPt, sPt, thPt, ny = 1):
            # makes the geodesic dome faces out of the points of an
            # icosahedron triangle
            b = self.a / ny # length of frequent triangles
            # =definition of direction vectors
            growVec = (sPt - fPt)
            # growVec = (fPt - sPt)
            growVec.multiply(1.0/ny)
            crossVec = (thPt - sPt)
            # crossVec = (sPt - thPt)
            crossVec.multiply(1.0/ny)

            for k in range(ny):
                kThirdPt = fPt + growVec * (k+0.0)
                dThirdPt = app.Vector(kThirdPt.x, kThirdPt.y, kThirdPt.z)
                dThirdPt = dThirdPt.normalize().multiply(domeRad.Value)
                kSecPt = fPt + growVec * (k+1.0)
                dSecPt = app.Vector(kSecPt.x, kSecPt.y, kSecPt.z)
                dSecPt = dSecPt.normalize().multiply(domeRad.Value)
                # thirdEdge = Part.makeLine(kSecPt, kThirdPt)
                # thirdEdge = Part.makeLine(dSecPt, dThirdPt)
                for l in range(k+1):
                    firstPt = kSecPt + crossVec *(l+1.0)
                    dFirstPt = firstPt.normalize().multiply(domeRad.Value)
                    secPt = kSecPt + crossVec *(l+0.0)
                    dSecPt =secPt.normalize().multiply(domeRad.Value)
                    thirdPt = kThirdPt + crossVec *(l+0.0)
                    dThirdPt = thirdPt.normalize().multiply(domeRad.Value)
                    #thirdEdge = Part.makeLine(secPt, thirdPt)
                    thirdEdge = Part.makeLine(dSecPt, dThirdPt)
                    # Part.show(thirdEdge)
                    if l > 0:
                        # What to do here?
                        #secEdge = Part.makeLine(oThirdPt,thirdPt)
                        secEdge = Part.makeLine(doThirdPt,dThirdPt)
                        # Part.show(secEdge)
                        #thirdEdge = Part.makeLine(secPt, thirdPt)
                        #thirdEdge = Part.makeLine(dSecPt, dThirdPt)
                        # Part.show(thirdEdge)
                        triWire = Part.Wire([firstEdge, secEdge, thirdEdge])
                        # Part.show(triWire)
                        triFace = Part.Face(triWire)
                        self.domeFaces.append(triFace)
                        #Part.show(triFace)

                    oThirdPt = thirdPt
                    doThirdPt = oThirdPt.normalize().multiply(domeRad.Value)
                    # oFirstPt = firstPt
                    #firstEdge = Part.makeLine(thirdPt,firstPt)
                    firstEdge = Part.makeLine(dThirdPt,dFirstPt)
                    oFirstEdge = firstEdge
                    #secEdge = Part.makeLine(firstPt,secPt)
                    secEdge = Part.makeLine(dFirstPt,dSecPt)
                    #Part.show(firstEdge)
                    #Part.show(secEdge)
                    #Part.show(thirdEdge)
                    triWire = Part.Wire([firstEdge, secEdge, thirdEdge])
                    triFace = Part.Face(triWire)
                    self.domeFaces.append(triFace)
                    #Part.show(triFace)

        try:
            domeRad = app.Units.Quantity(domeRad_str)
            # self.a = Strutlength of underlying icosahedron:
            self.a=(4.0*domeRad.Value)/math.sqrt(2.0*math.sqrt(5.0)+10.0)

            # icoAngle: angle of vertices of icosahedron points
            # not a north or south pole
            self.icoAngle = math.atan(0.5)

            self.icoLat = domeRad.Value * math.sin(self.icoAngle)
            self.latRad = domeRad.Value * math.cos(self.icoAngle)
            self.ang36 = math.radians(36.0)
            # Calculation all points of the icosahedron
            self.icoPts = []
            self.icoPts.append(app.Vector(0.0, 0.0, domeRad.Value))
            for i in range(10):
                self.icoCos = self.latRad * math.cos(i*self.ang36)
                self.icoSin = self.latRad * math.sin(i*self.ang36)
                if i%2 == 0:
                    self.icoPts.append(app.Vector(self.icoSin, self.icoCos, self.icoLat))
                else:
                    self.icoPts.append(app.Vector(self.icoSin, self.icoCos, -self.icoLat))

            self.icoPts.append(app.Vector(0.0, 0.0, -domeRad.Value))

            # making the faces of the icosahedron

            self.icoFaces = [] # collects faces of the underlying icosahedron
            self.domeFaces = [] # collects the faces of the geodesic dome
            thirdPt = self.icoPts[9]
            thirdEdge = Part.makeLine(self.icoPts[0],thirdPt)
            for i in range(5):
                j = i*2+1
                firstEdge = Part.makeLine(thirdPt,self.icoPts[j])
                secEdge = Part.makeLine(self.icoPts[j],self.icoPts[0])
                triWire = Part.Wire([firstEdge, secEdge, thirdEdge])
                triFace = Part.Face(triWire)
                self.icoFaces.append(triFace)
                # Part.show(triFace)
                makeFreqFaces(self.icoPts[j], self.icoPts[0], thirdPt, ny)

                thirdEdge = Part.makeLine(self.icoPts[0],self.icoPts[j])
                thirdPt = self.icoPts[j]

            thirdPt = self.icoPts[9]
            secPt = self.icoPts[10]
            thirdEdge = Part.makeLine(secPt,thirdPt)
            for i in range(10):
                j = i+1
                firstEdge = Part.makeLine(thirdPt,self.icoPts[j])
                secEdge = Part.makeLine(self.icoPts[j],secPt)
                triWire = Part.Wire([firstEdge, secEdge, thirdEdge])
                triFace = Part.Face(triWire)
                self.icoFaces.append(triFace)
                #Part.show(triFace)
                makeFreqFaces(self.icoPts[j], secPt, thirdPt, ny)

                thirdPt = secPt
                secPt = self.icoPts[j]
                thirdEdge = Part.makeLine(secPt,thirdPt)

            thirdPt = self.icoPts[10]
            thirdEdge = Part.makeLine(self.icoPts[11],thirdPt)
            for i in range(5):
                j = i*2+2
                firstEdge = Part.makeLine(thirdPt,self.icoPts[j])
                secEdge = Part.makeLine(self.icoPts[j],self.icoPts[11])
                triWire = Part.Wire([firstEdge, secEdge, thirdEdge])
                triFace = Part.Face(triWire)
                self.icoFaces.append(triFace)
                #Part.show(triFace)
                makeFreqFaces(self.icoPts[j], self.icoPts[11], thirdPt, ny)

                thirdEdge = Part.makeLine(self.icoPts[11],self.icoPts[j])
                thirdPt = self.icoPts[j]

            # Shell of a corresponding icosahedron
            newShell = Part.Shell(self.icoFaces)
            #Part.show(newShell)

            # Shell of the geodesic dome
            #self.domeShell = Part.Shell(self.domeFaces)
            #Part.show(self.domeShell)
            obj.Shape = Part.Shell(self.domeFaces)

            # Shere with radius of geodesic dome for debugging purposes
            testSphere = Part.makeSphere(domeRad.Value)
            #Part.show(testSphere)
        except Exception:
            sayexc(str(Exception))


try:
    d = QtGui.QWidget()
    d.ui = Ui_Dialog()
    d.ui.setupUi(d)
    d.ui.lineEdit_2.setText("2")
    d.ui.lineEdit.setProperty("text", "2 m")

    d.show()
except Exception as e:
    sayexc(str(Exception))
