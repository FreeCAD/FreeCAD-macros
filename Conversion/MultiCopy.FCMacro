##########################################################################################
#####				L I C E N S E					     #####
##########################################################################################
#
#  GNU LESSER GENERAL PUBLIC LICENSE
#  Version 2.1, February 1999
#
#  Copyright (C) 1991, 1999 Free Software Foundation, Inc.
#  51 Franklin Street, Fifth Floor, Boston, MA  02110-1301  USA
#  Everyone is permitted to copy and distribute verbatim copies
#  of this license document, but changing it is not allowed.
#
#  [This is the first released version of the Lesser GPL. It also counts
#  as the successor of the GNU Library Public License, version 2, hence
#  the version number 2.1.]
#
#  'MultiCopy' is a FreeCAD macro package. MultiCopy allows the duplication
#  (copy and paste) of multiple FreeCAD objects that can be labelled
#  sequentially and in a custom manner.
#
#  Copyright (C) 2021  Melwyn Francis Carlo
#
#  This library is free software; you can redistribute it and/or
#  modify it under the terms of the GNU Lesser General Public
#  License as published by the Free Software Foundation; either
#  version 2.1 of the License, or (at your option) any later version.
#
#  This library is distributed in the hope that it will be useful,
#  but WITHOUT ANY WARRANTY; without even the implied warranty of
#  MERCHANTABILITY or FITNESS FOR A PARTICULAR PURPOSE.  See the GNU
#  Lesser General Public License for more details.
#
#  You should have received a copy of the GNU Lesser General Public License
#  along with this library; if not, write to the Free Software Foundation, Inc.,
#  51 Franklin Street, Fifth Floor, Boston, MA  02110-1301, USA.
#
#  Contact Information :-
#  Email :  carlo.melwyn@outlook.com
#  FreeCAD UserTalk :  http://www.freecadweb.org/wiki/index.php?title=User:Melwyncarlo
#
##########################################################################################
#####				L I C E N S E					     #####
##########################################################################################
#
#
#
#  The MultiCopy macro was developed and tested on a platform containing the
#  following system and FreeCAD software specifications :
#
#  - OS			: Ubuntu 18.04.5 LTS (LXDE/Lubuntu)
#  - Word size of OS	: 64-bit
#  - Word size of FreeCAD: 64-bit
#  - Version		: 0.19
#  - Build type		: Release
#  - Branch		: unknown
#  - Hash		: 32200b604d421c4dad527fe587a7d047cf953b4f
#  - Python version	: 3.6.9
#  - Qt version		: 5.9.5
#  - Coin version	: 4.0.0a
#  - OCC version	: 7.3.0
#  - Locale		: English/UnitedKingdom (en_GB)



"""
  To use this macro, the steps to be followed are simple and straightforward :
  select one or more FreeCAD objects from the Tree view, and then select 'MultiCopy'.
  In the dialog box that pops up, choose the copy method, select and input the relevant
  paste parameters and commands, and then click on 'Paste'.

  Note (1)	The single underscore prefix (e.g. _name) denotes a private
		function or a private variable.
  Note (2)	Some of the short forms used in this script are as follows:
		  'mc' stands for MultiCopy
  		  'pcc' stands for Paste Code Commands
  		  'd' stands for Dialog (e.g. _d_, etc.)
"""



__Title__='MultiCopy'
__Author__='Melwyncarlo'
__Version__='2.0.0'
__Date__='2021-03-23'
__Comment__='MultiCopy allows the duplication (copy and paste) of multiple FreeCAD objects that can be labelled sequentially and in a custom manner.'
__Web__='https://github.com/melwyncarlo/MultiCopy'
__Wiki__='http://www.freecadweb.org/wiki/index.php?title=Macro_MultiCopy'
__Icon__='MultiCopy.svg'
__Help__='Select one or more FreeCAD objects, then click on the MultiCopy button/macro, and follow the instructions in the dialog box.'
__Status__='stable'
__Requires__='Freecad >= v0.17'
__Communication__='https://github.com/melwyncarlo/MultiCopy/issues'
__Files__='MultiCopy/MultiCopyGui.py, MultiCopy/MultiCopyCore.py, MultiCopy/MultiCopyAuxFunc.py, MultiCopy/resources/MultiCopy_Main_Dialog.ui, MultiCopy/resources/MultiCopy_Commands_Dialog.ui, MultiCopy/resources/MultiCopy.svg'




# Library Imports
#------------------------------------------------------------------------------------------------

import MultiCopy



###################################################################
###-------------------------------------------------------------###
### 			MULTICOPY MACRO CALLS			###
###-------------------------------------------------------------###
###								###
###	This is the main macro call. The code below commences 	###
###	the MultiCopy GUI interface. This script cannot be 	###
###	called externally.					###
								###
								###
if __name__ == '__main__':					###
	MultiCopy.Gui.Launch()					###
								###
###-------------------------------------------------------------###
### 			MULTICOPY MACRO CALLS	   		###
###-------------------------------------------------------------###
###################################################################
