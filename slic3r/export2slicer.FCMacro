# -*- coding: utf-8 -*-
# Opens current visible objects in Slic3r. One can use different slicing software

__Title__ = "Open in Slic3r"
__Author__ = "Damian Łoziński"
__Version__ = "0.1"
__Date__ = "2019-03-06"
__Comment__ = "Exports current visible objects to amf files and opens them in Slic3r"
__Web__ = ""
__Wiki__ = "http://www.freecadweb.org/wiki/index.php?title=Open in Slic3r"
__Icon__ = "/usr/lib/freecad/Mod/plugins/icons/Slic3r.png"
__Help__ = "Run this macro to open visible objects in slicer software. You may need to change slicer path"
__Status__ = ""
__Requires__ = "freecad 0.17"
__Communication__ = "https://github.com/dlozinski"
__Files__ = "Slic3r.png"

import os
import subprocess
import Mesh
import MeshPart
from SlcrDialogUtil import DialogUtil

# Slicing program executable. One can use different slicing software here and provide proper slicer executable location and custom flags
SLICER_CMD = ["/Applications/Original Prusa Drivers/PrusaSlicer.app/Contents/MacOS/PrusaSlicer"]

# You can format change to stl, but then all of the objects will be marged into single geometry
OUTPUT_FORMAT = "stl"

# Angular deflection in radians. Lower value = better quality of curved shapes and bigger file size
ANGULAR_DEFLECTION = 0.0872665


def get_filename(doc_filename):
	if doc_filename:
		dirname = os.path.dirname(doc_filename)
		filename = os.path.basename(doc_filename).partition('.')[0] + '.' + OUTPUT_FORMAT
		file_path = os.path.join(dirname, filename)
	else:
		file_path = "meshes-export." + OUTPUT_FORMAT
	return file_path

def main():
    doc = App.ActiveDocument
    if not doc:
        raise Exception("No active document")

    # Get all visible objests with shapes
    visible_shapes = (o for o in doc.Objects if o.ViewObject.isVisible() and hasattr(o, 'Shape'))

    # Ensure to not include both parent and child objects
    objects_to_export = set()
    for o in visible_shapes:
        if not set(o.InListRecursive).intersection(objects_to_export):
            objects_to_export.add(o)

    mesh_path = get_filename(doc.FileName)

    try:
        # Create temporary doc to store meshes so that we don't affect current doc history
        tmp_doc = App.newDocument("meshes")
        meshes = [m for m in doc.Objects if m.ViewObject.isVisible() and m.TypeId == 'Mesh::Feature']
        for o in objects_to_export:
            mesh = tmp_doc.addObject("Mesh::Feature", doc.Label)
            mesh.Mesh = MeshPart.meshFromShape(o.Shape, LinearDeflection=0.1, AngularDeflection=ANGULAR_DEFLECTION, Relative=False)
            meshes.append(mesh)

        if meshes:
            Mesh.export(meshes, mesh_path)
        else:
            raise Exception("No visible objects to export")
    finally:
        App.closeDocument("meshes")

    # Launch Slicer with meshes
    subprocess.Popen(SLICER_CMD + [mesh_path])
    App.Console.PrintMessage("Objects opened in Slicer: " + mesh_path)

try:
    main()
except Exception as e:
    DialogUtil.showErrorMessage(e)
